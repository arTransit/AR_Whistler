FME workspace _testLines.fmw

Parameters:
- DestDataset_SHAPE = C:\AndrewRoss\Work\AR_Whistler\Data   # Destination ESRI Shape Directory
- SourceDataset_SHAPE = C:\AndrewRoss\Work\AR_Whistler\Data\gfi_utm10.shp   # Source ESRI Shape File(s)

Readers:
- SHAPE_1: SHAPE from $(SourceDataset_SHAPE)

Writers:
- SHAPE_2: SHAPE to $(DestDataset_SHAPE) in UTM83-10

gfi_utm10 (reader SHAPE_1)
    attributes: BUS number(20,10), ROUTE number(20,10), TIMESTAMP number(20,10), DATE char(20), TIME char(20), BUSDAY number(20,10), SEQTR number(20,10), POINTCALC logical, SEQ number(20,10), N logical, TYPE number(20,10), SEQPPD number(20,10), TS char(20), LOC_N number(20,10), DES number(20,10), AMT number(20,10), ID number(20,10), SEQMISC number(20,10)
    -> Sorter
Sorter
    SORT_PARM = BUSDAY NUMERIC ASCENDING BUS NUMERIC ASCENDING ROUTE NUMERIC ASCENDING SEQTR NUMERIC ASCENDING
    SORTED -> PythonCaller_2
PythonCaller_2
    PYTHONSYMBOL = Points2lines.FMEPoints2lines
    PYTHONSOURCE:
      import fmeobjects
      # Template Function interface:
      def processFeature(feature):
         pass

      # Template Class Interface:
      class FeatureProcessor(object):
         def __init__(self):
             pass
         def input(self,feature):
             self.pyoutput(feature)
         def close(self):
             pass
    -> gfiLines (writer SHAPE_2)
gfiLines (writer SHAPE_2)
    attributes: TS char(20), DES char(20), LOC_N char(20), TIME char(20), DATE char(20), AMT char(20), TYPE number(20,10), N char(20), ID char(20), SEQMISC char(20), SEQ char(20), TIMESTAMP number(20,10), ROUTE number(20,10), BUS char(20), SEQPPD char(20), SEQTR char(20)
