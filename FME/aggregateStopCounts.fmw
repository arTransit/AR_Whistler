FME workspace aggregateStopCounts.fmw

Parameters:
- SourceDataset_SHAPE = C:\AndrewRoss\Work\AR_Whistler\Data\gfi_matchStops.shp   # Source ESRI Shape File(s)
- DestDataset_CSV = C:\AndrewRoss\Work\AR_Whistler\Data   # Destination Comma Separated Value (CSV) Directory
- DestDataset_SHAPE = C:\AndrewRoss\Work\AR_Whistler\Data   # Destination ESRI Shape Directory

Readers:
- SHAPE_1: SHAPE from $(SourceDataset_SHAPE)

Writers:
- CSV_1: CSV to $(DestDataset_CSV)
- SHAPE_2: SHAPE to $(DestDataset_SHAPE)

gfi_matchStops (reader SHAPE_1)
    attributes: STOPID number(20,0), POINTCALC logical, TS char(20), DATE char(20), TIME char(20), BUSDAY number(20,0), TIMESTAMP number(20,0), BUS number(20,0), ROUTE number(20,0), SEQTR number(20,0), DES char(20), LOC_N char(20), AMT number(20,10), TYPE number(20,0), N char(20), ID char(20), SEQMISC number(20,0), SEQ number(20,0), SEQPPD number(20,0)
    -> Tester
Tester
    TEST_DESCRIPTION = ""
    TEST_CLAUSE = TEST "@Value(STOPID)" > "0"
    BOOL_OP = OR
    TEST_MODE = Automatic
    PASSED -> AttributeCreator_2
    PASSED -> Aggregator_3
Aggregator_3
    ACCUM_ATTRS_NAME = No
    GROUP_BY = STOPID
    SEP = ,
    ORDERED = No
    CONTAIN_INDIVID_GEOMS = No
    AGGREGATE -> Deaggregator
Deaggregator
    PART_NUMBER_FIELD = _part_number
    RECURSIVE = No
    SPLIT_COMPOSITES = No
    DEAGGREGATED -> Tester_3
Tester_3
    TEST_DESCRIPTION = ""
    TEST_CLAUSE = TEST "@Value(_part_number)" = "0"
    BOOL_OP = OR
    TEST_MODE = Automatic
    PASSED -> FeatureMerger [input 1]
AttributeCreator_2
    ATTR_LIST = _TMPTIME,@Value(TIME)
    -> DateFormatter
DateFormatter
    FMT = %H
    DATE_ATTR = _TMPTIME
    -> Tester_2
Tester_2
    TEST_DESCRIPTION = ""
    TEST_CLAUSE = TEST "@Value(_TMPTIME)" < "6"
    BOOL_OP = OR
    TEST_MODE = Automatic
    PASSED -> Aggregator
    FAILED -> Tester_4
Aggregator
    ACCUM_ATTRS_NAME = No
    GROUP_BY = STOPID
    SEP = ,
    ORDERED = No
    CONTAIN_INDIVID_GEOMS = No
    COUNT_ATTR = COUNT_0006
    AGGREGATE -> FeatureMerger [input 2]
FeatureMerger
    REFEEATTR = STOPID
    MERGE_TYPE = Attributes Only
    PROCESS_DUPS = No
    BUILD_INCOMPLETE = No
    REFERATTR = STOPID
    COMPLETE -> FeatureMerger_2 [input 1]
    INCOMPLETE -> FeatureMerger_2 [input 1]
Tester_4
    TEST_DESCRIPTION = ""
    TEST_CLAUSE = TEST "@Value(_TMPTIME)" < "12"
    BOOL_OP = OR
    TEST_MODE = Automatic
    PASSED -> Aggregator_2
    FAILED -> Tester_5
Aggregator_2
    ACCUM_ATTRS_NAME = No
    GROUP_BY = STOPID
    SEP = ,
    ORDERED = No
    CONTAIN_INDIVID_GEOMS = No
    COUNT_ATTR = COUNT_0612
    AGGREGATE -> FeatureMerger_2 [input 2]
FeatureMerger_2
    REFEEATTR = STOPID
    MERGE_TYPE = Attributes Only
    PROCESS_DUPS = No
    BUILD_INCOMPLETE = No
    REFERATTR = STOPID
    COMPLETE -> FeatureMerger_3 [input 1]
    INCOMPLETE -> FeatureMerger_3 [input 1]
Tester_5
    TEST_DESCRIPTION = ""
    TEST_CLAUSE = TEST "@Value(_TMPTIME)" < "18"
    BOOL_OP = OR
    TEST_MODE = Automatic
    PASSED -> Aggregator_4
    FAILED -> Aggregator_5
Aggregator_4
    ACCUM_ATTRS_NAME = No
    GROUP_BY = STOPID
    SEP = ,
    ORDERED = No
    CONTAIN_INDIVID_GEOMS = No
    COUNT_ATTR = COUNT_1218
    AGGREGATE -> FeatureMerger_3 [input 2]
FeatureMerger_3
    REFEEATTR = STOPID
    MERGE_TYPE = Attributes Only
    PROCESS_DUPS = No
    BUILD_INCOMPLETE = No
    REFERATTR = STOPID
    COMPLETE -> FeatureMerger_4 [input 1]
    INCOMPLETE -> FeatureMerger_4 [input 1]
Aggregator_5
    ACCUM_ATTRS_NAME = No
    GROUP_BY = STOPID
    SEP = ,
    ORDERED = No
    CONTAIN_INDIVID_GEOMS = No
    COUNT_ATTR = COUNT_1800
    AGGREGATE -> FeatureMerger_4 [input 2]
FeatureMerger_4
    REFEEATTR = STOPID
    MERGE_TYPE = Attributes Only
    PROCESS_DUPS = No
    BUILD_INCOMPLETE = No
    REFERATTR = STOPID
    COMPLETE -> stopGFIcount (writer CSV_1)
    INCOMPLETE -> stopGFIcount (writer CSV_1)
    INCOMPLETE -> NullAttributeReplacer
    COMPLETE -> NullAttributeReplacer
stopGFIcount (writer CSV_1)
    attributes: STOPID number(20,0), COUNT_1800 char(20), COUNT_0612 char(20), COUNT_0006 char(20), COUNT_1218 char(20)
NullAttributeReplacer
    NEW_VALUE = 0
    SRC_ATTRS = COUNT_0006,COUNT_0612,COUNT_1218,COUNT_1800
    -> AttributeCreator
AttributeCreator
    ATTR_LIST = TOTALCOUNT,@Evaluate(@Value(COUNT_0006)+@Value(COUNT_0612)+@Value(COUNT_1218)+@Value(COUNT_1800))
    -> stopGFIcount (writer SHAPE_2)
stopGFIcount (writer SHAPE_2)
    attributes: STOPID number(20,0), COUNT_1800 number(20,0), COUNT_0612 number(20,0), COUNT_0006 number(20,0), COUNT_1218 number(20,0), TOTALCOUNT number(20,0)

FME custom transformer DateConverter
This transformer will convert dates between two user configurable formats
This transformer take three parameters:
    Source attribute: Attribute to convert
    Input Format: Format string describing the input date format. This transformer uses the Python time directives, listed below.
    Output format: Format string describing the output date format.
    Directive
    Meaning
%a Locale’s abbreviated weekday name. 
%A Locale’s full weekday name. 
%b Locale’s abbreviated month name. 
%B Locale’s full month name. 
%c Locale’s appropriate date and time representation. 
%d Day of the month as a decimal number [01,31]. 
%H Hour (24-hour clock) as a decimal number [00,23]. 
%I Hour (12-hour clock) as a decimal number [01,12]. 
%j Day of the year as a decimal number [001,366]. 
%m Month as a decimal number [01,12]. 
%M Minute as a decimal number [00,59]. 
%p Locale’s equivalent of either AM or PM.
%S Second as a decimal number [00,61].
%U Week number of the year (Sunday as the first day of the week) as a decimal number [00,53]. All days in a new year preceding the first Sunday are considered to be in week 0.
%w Weekday as a decimal number [0(Sunday),6]. 
%W Week number of the year (Monday as the first day of the week) as a decimal number [00,53]. All days in a new year preceding the first Monday are considered to be in week 0.
%x Locale’s appropriate date representation. 
%X Locale’s appropriate time representation. 
%y Year without century as a decimal number [00,99]. 
%Y Year with century as a decimal number. 
%Z Time zone name (no characters if no time zone exists). 
%% A literal '%' character.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTR =   # Source Attribute
- IN_FMT =   # Input Format
- OUT_FMT =   # Output Format

INPUT (input)
    -> SubstringExtractor
Note: Get source attribute / with dialog
SubstringExtractor
    SRC_ATTR = $(SRC_ATTR)
    END = -1
    START = 0
    RESULT_ATTR = _DateConverter_in_date
    -> ParameterFetcher
Note: Get in/out formats
ParameterFetcher
    ATTR_LIST = _DateConverter_SRC_ATTR {$(SRC_ATTR)} _DateConverter_IN_FMT {$(IN_FMT)} _DateConverter_OUT_FMT {$(OUT_FMT)}
    -> PythonCaller
Note: Convert date
PythonCaller
    PYTHONSYMBOL = convertDate
    PYTHONSOURCE:
      import fmeobjects
      import time
      # Template Function interface:
      def convertDate(feature):
         # get input date
         inDate = feature.getAttribute('_DateConverter_in_date')
         # get input format
         inFormat = feature.getAttribute('_DateConverter_IN_FMT')
         # get output format
         outFormat = feature.getAttribute('_DateConverter_OUT_FMT')
         #get output attribute name
         outAttr = feature.getAttribute('_DateConverter_SRC_ATTR')
         # convert date
         t = time.strptime(inDate,inFormat)
         outDate = time.strftime(outFormat,t)
         # set date as new attribute
         feature.setAttribute(outAttr,outDate)
    -> AttributeRemover
Note: Clean up attributes
AttributeRemover
    REMOVE_ATTRS = _DateConverter_in_date,_DateConverter_SRC_ATTR,_DateConverter_IN_FMT,_DateConverter_OUT_FMT
    -> OUTPUT (output)
OUTPUT (output)
