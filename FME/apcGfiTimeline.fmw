FME workspace apcGfiTimeline.fmw

Parameters:
- DestDataset_FILEGDB = C:\AndrewRoss\Work\AR_Whistler\Data\tmp.gdb   # File Geodatabase|*.gdb Destination Geodatabase

Writers:
- FILEGDB_1: FILEGDB to $(DestDataset_FILEGDB)

APC: SQLCreator
    FORMAT = SQLITE3
    DATASET = C:\AndrewRoss\Work\AR_Whistler\Data\whistlerData02.db
    SQL_STATEMENT = select * from V_APCGOOD
    EXPOSED_ATTRIBUTE_LIST = ALT,BUSDAY,BUSID,DATE,DATETIME,KEYID,LATITUDE,LONGITUDE,TIME,TIMESTAMP,TYPE
    RESULT -> 2DPointReplacer_2
2DPointReplacer_2
    YVALATTR = (@Value(BUSID)*400)
    XVALATTR = @Value(TIMESTAMP)
    POINT -> apc_timestamp (writer FILEGDB_1)
apc_timestamp (writer FILEGDB_1)
    attributes: LONGITUDE double, ALT double, DATE text(20), TIME text(20), DATETIME text(20), TYPE text(20), BUSDAY int, BUSID int, KEYID text(20), TIMESTAMP int, LATITUDE double
GFI: SQLCreator
    FORMAT = SQLITE3
    DATASET = C:\AndrewRoss\Work\AR_Whistler\Data\whistlerData02.db
    SQL_STATEMENT = select * from V_GFI_APCBUS
    EXPOSED_ATTRIBUTE_LIST = BUS,BUSDAY,DES,ID,LOC_N,N,ROUTE,SEQ,SEQPPD,SEQTR,TIMESTAMP,TS,TYPE,AMT
    RESULT -> 2DPointReplacer
2DPointReplacer
    YVALATTR = (@Value(BUS)*400)+50
    XVALATTR = @Value(TIMESTAMP)
    POINT -> gfi_timestamp (writer FILEGDB_1)
gfi_timestamp (writer FILEGDB_1)
    attributes: DES int, TS text(20), LOC_N int, AMT double, N int, TYPE int, BUSDAY int, ID int, SEQ int, TIMESTAMP int, BUS int, ROUTE int, SEQPPD int, SEQTR int
