FME workspace calculcateTelemetry.fmw

Parameters:
- SourceDataset_SHAPE = C:\AndrewRoss\Work\AR_Whistler\Data\gfi_utm10.shp   # Source ESRI Shape File(s)
- DestDataset_SHAPE = C:\AndrewRoss\Work\AR_Whistler\Data   # Destination ESRI Shape Directory

Readers:
- SHAPE_1: SHAPE from $(SourceDataset_SHAPE)

Writers:
- SHAPE_2: SHAPE to $(DestDataset_SHAPE)

gfi_utm10 (reader SHAPE_1)
    attributes: BUS number(20,10), ROUTE number(20,10), TIMESTAMP number(20,10), DATE char(20), TIME char(20), BUSDAY number(20,10), SEQTR number(20,10), POINTCALC logical, SEQ number(20,10), N logical, TYPE number(20,10), SEQPPD number(20,10), TS char(20), LOC_N number(20,10), DES number(20,10), AMT number(20,10), ID number(20,10), SEQMISC number(20,10)
    -> Sorter
Sorter
    SORT_PARM = BUSDAY NUMERIC ASCENDING BUS NUMERIC ASCENDING ROUTE NUMERIC ASCENDING SEQTR NUMERIC ASCENDING
    SORTED -> PythonCaller
PythonCaller
    NEW_ATTRIBUTES = DISTANCE BEARING SPEED ELAPSED DTREND
    PYTHONSYMBOL = CalculateTelemetry.FMETelemetry
    -> gfi_telemetry (writer SHAPE_2)
gfi_telemetry (writer SHAPE_2)
    attributes: SEQ char(20), N char(20), TYPE char(20), SEQPPD char(20), TS char(20), LOC_N char(20), DES char(20), AMT char(20), ID char(20), DATE char(20), TIME char(20), TIMESTAMP char(20), SEQMISC char(20), BUSDAY char(20), ROUTE char(20), BUS char(20), SEQTR char(20), POINTCALC char(20), BEARING number(20,10), DISTANCE number(20,10), SPEED number(20,10), ELAPSED number(20,10), DTREND number(20,10)
