FME workspace checkAPCopenclose.fmw

Parameters:
- SourceDataset_SHAPE = C:\AndrewRoss\Basedata\Transit\Stops\BusStops.shp   # Source ESRI Shape File(s)
- DestDataset_SHAPE = C:\AndrewRoss\Work\AR_Whistler\Data   # Destination ESRI Shape Directory

Readers:
- SHAPE_1: SHAPE from $(SourceDataset_SHAPE)

Writers:
- SHAPE_2: SHAPE to $(DestDataset_SHAPE)

APC: SQLCreator
    FORMAT = SQLITE3
    DATASET = C:\AndrewRoss\Work\AR_Whistler\Data\whistlerData02.db
    SQL_STATEMENT = select * from V_APCGOOD
    EXPOSED_ATTRIBUTE_LIST = ALT,BUSDAY,BUSID,DATE,DATETIME,KEYID,LATITUDE,LONGITUDE,TIME,TIMESTAMP,TYPE
    RESULT -> Tester
Tester
    TEST_DESCRIPTION = ""
    TEST_CLAUSE = TEST "@Value(TYPE)" IN "O,C"
    BOOL_OP = OR
    TEST_MODE = Automatic
    PASSED -> Sorter
Sorter
    SORT_PARM = BUSID NUMERIC ASCENDING TIMESTAMP NUMERIC ASCENDING
    SORTED -> 2DPointReplacer
2DPointReplacer
    YVALATTR = @Value(LATITUDE)
    XVALATTR = @Value(LONGITUDE)
    POINT -> Reprojector
Reprojector
    DEST = BCALB-83
    SOURCE = LL
    RASTER_CELL_SIZE = Preserve Cells
    INTERPOLATION_TYPE_NAME = Nearest Neighbor
    STROKE_ARCS = Yes
    REPROJECTED -> NeighborFinder [input 1]
BusStops (reader SHAPE_1)
    attributes: STOPID number(7,0), STOPNAME char(75), STOPCLASS number(2,0), LATITUDE number(15,10), LONGITUDE number(15,10), STATUS char(14), BCTREGION char(35), REGDIST char(35), BCTSYSTEM char(35), EXCHANGE char(35), PARKNRIDE char(35), AREANAME char(35), ADDNUMBER number(6,0), ADDSTREET char(35), ADDCITY char(35), STOPOWNER char(35), STOPRESP char(1), SBOWNER char(35), SBRESP char(35), BSSIGNAGE number(2,0), STOPIDDIS number(2,0), SIGNPOST number(2,0), SCHEDHOLD number(2,0), RTID number(2,0), BENCH number(2,0), SHELTER number(2,0), MAPDISPLAY number(2,0), ADVERT number(2,0), GARBAGEBIN number(2,0), HEATING number(2,0),
      LIGHTING number(2,0), SHADE number(2,0), ACCESSIBLE number(2,0), SURFACE number(2,0), CSD number(2,0), CURBHEIGHT number(3,0), CPLA number(2,0), TGSI number(2,0), SIDEWALK number(2,0), COMMENTS char(254), MODDATE date
    -> NeighborFinder [input 2]
NeighborFinder
    MAX = 50
    CANDIDATES_FIRST = No
    TREAT_POLYGON_AS = Lines
    INSERT_VERTEX = No
    MATCHED -> NeighborFinder_MATCHED
    UNMATCHED_BASE -> NeighborFinder_UNMATCHED_BASE
    MATCHED -> apc_stop (writer SHAPE_2)
    UNMATCHED_BASE -> apc_nostop (writer SHAPE_2)
apc_stop (writer SHAPE_2)
    attributes: _DISTANCE number(20,10), LATITUDE number(20,10), DATETIME char(20), BUSDAY number(20,0), STOPID number(20,0), BUSID number(20,0), LONGITUDE number(20,10), TIME char(20), TYPE char(20), DATE char(20), TIMESTAMP number(20,0), KEYID char(20), ALT number(20,10)
NeighborFinder_MATCHED: Inspector
apc_nostop (writer SHAPE_2)
    attributes: _DISTANCE number(20,10), LATITUDE number(20,10), DATETIME char(20), BUSDAY number(20,0), STOPID number(20,0), BUSID number(20,0), LONGITUDE number(20,10), TIME char(20), TYPE char(20), DATE char(20), TIMESTAMP number(20,0), KEYID char(20), ALT number(20,10)
NeighborFinder_UNMATCHED_BASE: Inspector
