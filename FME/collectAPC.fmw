FME workspace collectAPC.fmw

Parameters:
- SourceDataset_CSV_3 = \\vtcapc2010v1\APCDATA\APC\Whistler\data_nova\2013*\*.dat   # Source Comma Separated Value (CSV) File(s)
- DestDataset_SQLITE3 = C:\AndrewRoss\Work\AR_Whistler\Data\whistlerData02.db   # Destination SQLite3 Database File

Readers:
- CSV_2: CSV from $(SourceDataset_CSV_3)

Writers:
- SQLITE3_1: SQLITE3 to $(DestDataset_SQLITE3)

9302 (reader CSV_2)
    attributes: col0 char(11), col1 char(9), col2 number(8,5), col3 number(10,5), col4 char(255), col5 char(72), col6 char(1)
    -> AttributeRenamer
9303 (reader CSV_2)
    attributes: col0 char(11), col1 char(9), col2 number(8,5), col3 number(10,5), col4 number(9,5), col5 char(72), col6 char(1)
    -> AttributeRenamer
9304 (reader CSV_2)
    attributes: col0 char(11), col1 char(9), col2 number(8,5), col3 number(10,5), col4 number(9,5), col5 char(72), col6 char(1)
    -> AttributeRenamer
AttributeRenamer
    ATTR_LIST = col0,DATE,"",col1,TIME,"",col2,LATITUDE,"",col3,LONGITUDE,"",col4,ALT,"",col5,DATA,"",fme_basename,BUSID,""
    -> FilterLatLon
FilterLatLon: Tester
    TEST_DESCRIPTION = ""
    TEST_CLAUSE:
      TEST "@Value(LATITUDE)" > "0"
      TEST "@Evaluate(abs(@Value(LONGITUDE)))" > "0"
    BOOL_OP = AND
    TEST_MODE = Automatic
    PASSED -> AttributeRemover
AttributeRemover
    REMOVE_ATTRS = col6
    -> StringConcatenator
StringConcatenator
    PARM_LINE = @Value(DATE) @Value(TIME)
    VAL_ATTR = DATETIME
    -> AttributeCopier
AttributeCopier
    ATTR_LIST = _TIMESTAMP,DATETIME
    -> DateFormatter
DateFormatter
    FMT = %s
    DATE_ATTR = _TIMESTAMP
    -> AttributeCreator_3
AttributeCreator_3
    ATTR_LIST = TIMESTAMP,@Evaluate((@Value(_TIMESTAMP) -(8*60*60)))
    -> Tester_2
Tester_2
    TEST_DESCRIPTION = ""
    TEST_CLAUSE:
      TEST "@Value(TIMESTAMP)" >= "1359349200"
      TEST "@Value(TIMESTAMP)" <= "1360645200"
    BOOL_OP = AND
    TEST_MODE = Automatic
    PASSED -> AttributeCreator_5
AttributeCreator_5
    ATTR_LIST = BUSDAY,@Evaluate(int((@Value(TIMESTAMP) -(5*60*60)) / (24*60*60)))
    -> SubstringExtractor
SubstringExtractor
    SRC_ATTR = DATA
    END = 1
    START = 1
    RESULT_ATTR = TYPE
    -> Tester_3
Tester_3
    TEST_DESCRIPTION = ""
    TEST_CLAUSE = TEST "@Value(TYPE)" NOT_LIKE "D"
    BOOL_OP = OR
    TEST_MODE = Automatic
    PASSED -> APC_RAW (writer SQLITE3_1)
APC_RAW (writer SQLITE3_1)
    attributes: DATETIME varchar(20), TIMESTAMP integer, BUSID integer, LATITUDE float, LONGITUDE float, ALT float, DATE varchar(20), TIME varchar(20), BUSDAY integer, TYPE varchar(5)

FME custom transformer DateConverter
This transformer will convert dates between two user configurable formats
This transformer take three parameters:
    Source attribute: Attribute to convert
    Input Format: Format string describing the input date format. This transformer uses the Python time directives, listed below.
    Output format: Format string describing the output date format.
    Directive
    Meaning
%a Locale’s abbreviated weekday name. 
%A Locale’s full weekday name. 
%b Locale’s abbreviated month name. 
%B Locale’s full month name. 
%c Locale’s appropriate date and time representation. 
%d Day of the month as a decimal number [01,31]. 
%H Hour (24-hour clock) as a decimal number [00,23]. 
%I Hour (12-hour clock) as a decimal number [01,12]. 
%j Day of the year as a decimal number [001,366]. 
%m Month as a decimal number [01,12]. 
%M Minute as a decimal number [00,59]. 
%p Locale’s equivalent of either AM or PM.
%S Second as a decimal number [00,61].
%U Week number of the year (Sunday as the first day of the week) as a decimal number [00,53]. All days in a new year preceding the first Sunday are considered to be in week 0.
%w Weekday as a decimal number [0(Sunday),6]. 
%W Week number of the year (Monday as the first day of the week) as a decimal number [00,53]. All days in a new year preceding the first Monday are considered to be in week 0.
%x Locale’s appropriate date representation. 
%X Locale’s appropriate time representation. 
%y Year without century as a decimal number [00,99]. 
%Y Year with century as a decimal number. 
%Z Time zone name (no characters if no time zone exists). 
%% A literal '%' character.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTR =   # Source Attribute
- IN_FMT =   # Input Format
- OUT_FMT =   # Output Format

INPUT (input)
    -> SubstringExtractor
Note: Get source attribute / with dialog
SubstringExtractor
    SRC_ATTR = $(SRC_ATTR)
    END = -1
    START = 0
    RESULT_ATTR = _DateConverter_in_date
    -> ParameterFetcher
Note: Get in/out formats
ParameterFetcher
    ATTR_LIST = _DateConverter_SRC_ATTR {$(SRC_ATTR)} _DateConverter_IN_FMT {$(IN_FMT)} _DateConverter_OUT_FMT {$(OUT_FMT)}
    -> PythonCaller
Note: Convert date
PythonCaller
    PYTHONSYMBOL = convertDate
    PYTHONSOURCE:
      import fmeobjects
      import time
      # Template Function interface:
      def convertDate(feature):
         # get input date
         inDate = feature.getAttribute('_DateConverter_in_date')
         # get input format
         inFormat = feature.getAttribute('_DateConverter_IN_FMT')
         # get output format
         outFormat = feature.getAttribute('_DateConverter_OUT_FMT')
         #get output attribute name
         outAttr = feature.getAttribute('_DateConverter_SRC_ATTR')
         # convert date
         t = time.strptime(inDate,inFormat)
         outDate = time.strftime(outFormat,t)
         # set date as new attribute
         feature.setAttribute(outAttr,outDate)
    -> AttributeRemover
Note: Clean up attributes
AttributeRemover
    REMOVE_ATTRS = _DateConverter_in_date,_DateConverter_SRC_ATTR,_DateConverter_IN_FMT,_DateConverter_OUT_FMT
    -> OUTPUT (output)
OUTPUT (output)

FME custom transformer bingo

INPUT (input)
OUTPUT (output)
