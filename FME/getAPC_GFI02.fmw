FME workspace getAPC_GFI02.fmw

Parameters:
- DestDataset_SQLITE3 = C:\AndrewRoss\Work\AR_Whistler\Data\whistlerData02.db   # Destination SQLite3 Database File

Writers:
- SQLITE3_1: SQLITE3 to $(DestDataset_SQLITE3)

SQLCreator [off]
    ORACLE8I_DB_REMOVE_SCHEMA_QUALIFIER = NO
    FORMAT = ORACLE8I_DB
    DATASET = APCTEST
    SQL_STATEMENT:
      select KEYID,DATETIME,SERVICEDATE,SERVICETIME,DAYOFWEEK,SERVICEDAYOFWEEK,
      LATITUDE,LONGITUDE,ELEVATION,
      EVENT, RECORDID,BUSID,SYSTEM from STAGING_APCRAW
      where SYSTEM='WHISTLER'
      and DATETIME between to_date('2013-01-28 00:00:00', 'YYYY-MM-DD HH24:MI:SS')
      and to_date('2013-02-12 12:00:00', 'YYYY-MM-DD HH24:MI:SS')
    ORACLE8I_DB_USER_NAME = apc
    EXPOSED_ATTRIBUTE_LIST = BUSID,DATETIME,DATETIME.full,DAYOFWEEK,ELEVATION,EVENT,KEYID,LATITUDE,LONGITUDE,RECORDID,SERVICEDATE,SERVICEDAYOFWEEK,SERVICETIME,SYSTEM
    ORACLE8I_DB_SERVER_TYPE = ORACLE8i
    ORACLE8I_DB_PASSWORD = apc
    RESULT -> AttributeCopier_2
AttributeCopier_2 [off]
    ATTR_LIST = _TIMESTAMP,DATETIME.full
    -> DateFormatter_3
DateFormatter_3 [off]
    FMT = %Y-%m-%d %H:%M:%S
    DATE_ATTR = DATETIME.full
    -> DateFormatter
DateFormatter [off]
    FMT = %s
    DATE_ATTR = _TIMESTAMP
    -> AttributeCreator_4
AttributeCreator_4 [off]
    ATTR_LIST = TIMESTAMP,@Evaluate(@Evaluate(@Value(_TIMESTAMP) -(8*60*60)))
    -> AttributeCreator_5
AttributeCreator_5 [off]
    ATTR_LIST = BUSDAY,@Evaluate(int((@Value(TIMESTAMP) -(5*60*60)) / (24*60*60)))
    -> APC (writer SQLITE3_1)
APC (writer SQLITE3_1) [off]
    attributes: KEYID varchar(20), DATESTRING varchar(20), BUSDAY integer,indexed, TIMESTAMP integer,indexed, SERVICEDATE varchar(20), DAYOFWEEK integer, SERVICEDAYOFWEEK integer, LATITUDE float, LONGITUDE float, ELEVATION float, EVENT varchar(9), BUSID integer,indexed, SYSTEM varchar(20), RECORDID integer, SERVICETIME varchar(20)
SQLCreator_2
    ORACLE8I_DB_REMOVE_SCHEMA_QUALIFIER = NO
    FORMAT = ORACLE8I_DB
    DATASET = GFI
    SQL_STATEMENT:
      SELECT tr.loc_n,tr.id,tr.tr_seq SEQTR,ppd.tr_seq SEQPPD,trmisc.tr_seq SEQMISC,
      TO_CHAR(tr.ts,'YYYY-MM-DD HH24:MI:SS') TS,tr.type,tr.bus,tr.route,tr.n,ppd.seq,ppd.des, trmisc.amt
      FROM tr LEFT OUTER JOIN ppd ON tr.loc_n=ppd.loc_n AND tr.id=ppd.id AND tr.tr_seq=ppd.tr_seq
      LEFT OUTER JOIN trmisc ON tr.loc_n=trmisc.loc_n AND tr.id=trmisc.id AND tr.tr_seq=trmisc.tr_seq
      WHERE tr.ts between to_date('2013-01-28 00:00:00', 'YYYY-MM-DD HH24:MI:SS')
      and to_date('2013-02-12 12:00:00', 'YYYY-MM-DD HH24:MI:SS')
      AND tr.loc_n IN (3)
      ORDER BY tr.bus,tr.id,tr.tr_seq ASC
    ORACLE8I_DB_USER_NAME = gfi
    EXPOSED_ATTRIBUTE_LIST = LOC_N,ID,SEQTR,SEQPPD,SEQMISC,TS,TYPE,BUS,ROUTE,N,SEQ,DES,AMT
    ORACLE8I_DB_SERVER_TYPE = ORACLE8i
    ORACLE8I_DB_PASSWORD = gfi
    RESULT -> AttributeCopier
AttributeCopier
    ATTR_LIST = _TIMESTAMP,TS
    -> DateFormatter_2
DateFormatter_2
    FMT = %s
    DATE_ATTR = _TIMESTAMP
    -> AttributeCreator_3
AttributeCreator_3
    ATTR_LIST = TIMESTAMP,@Evaluate((@Value(_TIMESTAMP) -(8*60*60)))
    -> AttributeCreator
AttributeCreator
    ATTR_LIST:
      BUSDAY,@Evaluate(int((@Value(TIMESTAMP) -(5*60*60)) / (24*60*60))
      )
    -> GFI (writer SQLITE3_1)
GFI (writer SQLITE3_1)
    attributes: LOC_N integer, ID integer, SEQTR integer,indexed, SEQPPD integer, SEQMISC integer, TS varchar(20),indexed, TIMESTAMP integer, BUSDAY integer, TYPE integer, BUS integer,indexed, ROUTE integer,indexed, N integer, SEQ integer,indexed, DES integer, AMT float
