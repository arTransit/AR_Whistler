FME workspace matchGFIAPC_openclose.fmw

Parameters:
- DestDataset_SQLITE3 = C:\AndrewRoss\Work\AR_Whistler\Data\whistlerData02.db   # Destination SQLite3 Database File

Writers:
- SQLITE3_1: SQLITE3 to $(DestDataset_SQLITE3)

GFI: SQLCreator
    FORMAT = SQLITE3
    DATASET = C:\AndrewRoss\Work\AR_Whistler\Data\whistlerData02.db
    SQL_STATEMENT = "select * from V_GFI_APCBUS\n"
    EXPOSED_ATTRIBUTE_LIST = _ID,BUS,BUSDAY,DES,ID,LOC_N,N,ROUTE,SEQ,SEQPPD,SEQTR,TIMESTAMP,TS,TYPE
    RESULT -> AttributeCreator
AttributeCreator
    ATTR_LIST = _SOURCE,GFI
    -> Sorter
Sorter
    SORT_PARM = BUS NUMERIC ASCENDING BUSDAY NUMERIC ASCENDING ROUTE NUMERIC ASCENDING SEQTR NUMERIC ASCENDING
    SORTED -> PythonCaller
APC: SQLCreator
    FORMAT = SQLITE3
    DATASET = C:\AndrewRoss\Work\AR_Whistler\Data\whistlerData02.db
    SQL_STATEMENT = select * from V_APCGOOD
    EXPOSED_ATTRIBUTE_LIST = _ID,ALT,BUSDAY,BUSID,DATE,DATETIME,KEYID,LATITUDE,LONGITUDE,TIME,TIMESTAMP,TYPE
    RESULT -> Tester
Tester
    TEST_DESCRIPTION = ""
    TEST_CLAUSE = TEST "@Value(TYPE)" IN "O,C"
    BOOL_OP = OR
    TEST_MODE = Automatic
    PASSED -> AttributeCreator_2
AttributeCreator_2
    ATTR_LIST = _SOURCE,APC
    -> Sorter_2
Sorter_2
    SORT_PARM = BUSID NUMERIC ASCENDING BUSDAY NUMERIC ASCENDING TIMESTAMP NUMERIC ASCENDING
    SORTED -> PythonCaller
PythonCaller
    NEW_ATTRIBUTES = _APCMATCHID
    PYTHONSYMBOL = Whistler.FMEmatchAPC
    -> GFImatch (writer SQLITE3_1)
GFImatch (writer SQLITE3_1)
    attributes: _ID integer, _APCMATCHID integer
