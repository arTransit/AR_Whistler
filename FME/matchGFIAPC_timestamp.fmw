FME workspace matchGFIAPC_timestamp.fmw

Parameters:
- DestDataset_SQLITE3 = C:\AndrewRoss\Work\AR_Whistler\Data\whistlerData02.db   # Destination SQLite3 Database File

Writers:
- SQLITE3_1: SQLITE3 to $(DestDataset_SQLITE3)

APC: SQLCreator
    FORMAT = SQLITE3
    DATASET = C:\AndrewRoss\Work\AR_Whistler\Data\whistlerData02.db
    SQL_STATEMENT = select * from V_APCGOOD
    EXPOSED_ATTRIBUTE_LIST = _ID,ALT,BUSDAY,BUSID,DATE,DATETIME,KEYID,LATITUDE,LONGITUDE,TIME,TIMESTAMP,TYPE
    RESULT -> AttributeCreator
AttributeCreator
    ATTR_LIST = _SOURCE,APC
    -> 2DPointReplacer
2DPointReplacer
    YVALATTR = @Value(LATITUDE)
    XVALATTR = @Value(LONGITUDE)
    POINT -> Reprojector
Reprojector
    DEST = UTM83-10
    SOURCE = LL
    RASTER_CELL_SIZE = Preserve Cells
    INTERPOLATION_TYPE_NAME = Nearest Neighbor
    STROKE_ARCS = Yes
    REPROJECTED -> Sorter_2
Sorter_2
    SORT_PARM = BUS NUMERIC ASCENDING TIMESTAMP NUMERIC ASCENDING
    SORTED -> PythonCaller
GFI: SQLCreator
    FORMAT = SQLITE3
    DATASET = C:\AndrewRoss\Work\AR_Whistler\Data\whistlerData02.db
    SQL_STATEMENT = select * from V_GFI_APCBUS
    EXPOSED_ATTRIBUTE_LIST = _ID,BUS,BUSDAY,DES,ID,LOC_N,N,ROUTE,SEQ,SEQPPD,SEQTR,TIMESTAMP,TS,TYPE,AMT,SEQMISC,SEQ
    RESULT -> AttributeCreator_2
AttributeCreator_2
    ATTR_LIST = _SOURCE,GFI
    -> Sorter
Sorter
    SORT_PARM = BUS NUMERIC ASCENDING TIMESTAMP NUMERIC ASCENDING
    SORTED -> PythonCaller
PythonCaller
    NEW_ATTRIBUTES = _STATUS POINTCALC TIMEDIFF
    PYTHONSYMBOL = Interpolate.FMEInterpolatePoints3
    PYTHONSOURCE:
      import fmeobjects
      # Template Function interface:
      def processFeature(feature):
         pass

      # Template Class Interface:
      class FeatureProcessor(object):
         def __init__(self):
             pass
         def input(self,feature):
             self.pyoutput(feature)
         def close(self):
             pass
    -> Tester
Tester
    TEST_DESCRIPTION = ""
    TEST_CLAUSE = TEST "@Value(_STATUS)" = "1"
    BOOL_OP = OR
    TEST_MODE = Automatic
    PASSED -> GFImatchTimestamp (writer SQLITE3_1)
GFImatchTimestamp (writer SQLITE3_1)
    attributes: _ID integer, LATITUDE float, LONGITUDE float, POINTCALC integer, TIMEDIFF float
