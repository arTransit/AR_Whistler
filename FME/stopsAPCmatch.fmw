FME workspace stopsAPCmatch.fmw

Parameters:
- SourceDataset_SHAPE = C:\AndrewRoss\Basedata\Transit\Stops\BusStops.shp   # Source ESRI Shape File(s)
- DestDataset_SQLITE3 = C:\AndrewRoss\Work\AR_Whistler\Data\whistlerData02.db   # Destination SQLite3 Database File

Readers:
- SHAPE_1: SHAPE from $(SourceDataset_SHAPE)

Writers:
- SQLITE3_1: SQLITE3 to $(DestDataset_SQLITE3)

SQLCreator
    FORMAT = SQLITE3
    DATASET = C:\AndrewRoss\Work\AR_Whistler\Data\whistlerData02.db
    SQL_STATEMENT = select * from APC  where EVENT in ('O')
    EXPOSED_ATTRIBUTE_LIST = KEYID,LATITUDE,LONGITUDE
    RESULT -> 2DPointReplacer
2DPointReplacer
    YVALATTR = @Value(LATITUDE)
    XVALATTR = @Value(LONGITUDE)
    POINT -> Reprojector
Reprojector
    DEST = BCALB-83
    SOURCE = LL
    RASTER_CELL_SIZE = Preserve Cells
    INTERPOLATION_TYPE_NAME = Nearest Neighbor
    STROKE_ARCS = Yes
    REPROJECTED -> NeighborFinder [input 1]
BusStops (reader SHAPE_1)
    attributes: STOPID number(7,0), STOPNAME char(75), STOPCLASS number(2,0), LATITUDE number(15,10), LONGITUDE number(15,10), STATUS char(14), BCTREGION char(35), REGDIST char(35), BCTSYSTEM char(35), EXCHANGE char(35), PARKNRIDE char(35), AREANAME char(35), ADDNUMBER number(6,0), ADDSTREET char(35), ADDCITY char(35), STOPOWNER char(35), STOPRESP char(1), SBOWNER char(35), SBRESP char(35), BSSIGNAGE number(2,0), STOPIDDIS number(2,0), SIGNPOST number(2,0), SCHEDHOLD number(2,0), RTID number(2,0), BENCH number(2,0), SHELTER number(2,0), MAPDISPLAY number(2,0), ADVERT number(2,0), GARBAGEBIN number(2,0), HEATING number(2,0),
      LIGHTING number(2,0), SHADE number(2,0), ACCESSIBLE number(2,0), SURFACE number(2,0), CSD number(2,0), CURBHEIGHT number(3,0), CPLA number(2,0), TGSI number(2,0), SIDEWALK number(2,0), COMMENTS char(254), MODDATE date
    -> NeighborFinder [input 2]
NeighborFinder
    MAX = 100
    CANDIDATES_FIRST = No
    TREAT_POLYGON_AS = Lines
    INSERT_VERTEX = No
    MATCHED -> stopsAPCmatch (writer SQLITE3_1)
stopsAPCmatch (writer SQLITE3_1)
    attributes: KEYID varchar(20), STOPID integer, _distance float
